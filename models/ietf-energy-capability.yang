module ietf-energy-capability {
  namespace "urn:ietf:params:xml:ns:yang:ietf-energy-capability";
  prefix ecap;

  import ietf-energy-core { prefix energy; }

  container energy-capability {
    list device {
      key "model";
      leaf model { type string; }
      leaf vendor { type string; }
      leaf rated-power { type decimal64 { fraction-digits 3; } units "W"; }
      leaf standby-power { type decimal64 { fraction-digits 3; } units "W"; }
      leaf efficiency-class { type string; description "From datasheet label (e.g., 80PLUS, EnergyStar)"; }
      leaf supported-power-states { type string; description "Comma-separated list of states"; }
      leaf transition-time { type uint32; units "ms"; description "Average transition time between power states"; }
      leaf accuracy-class { type string; description "± tolerance"; }
    }
  }
}
